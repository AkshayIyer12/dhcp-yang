module dhcp {
  namespace "http://yang-central.org/ns/example/dhcp";
  prefix dhcp;
  
  import ietf-yang-types { prefix yang; }
  import ietf-inet-types { prefix inet; }
  
  type yang: date-and-time;
  
  organization
    "yang-central.org";
  description
    "Partial data model for DHCP, based on the config of
     the ISC dhcp reference implementation.";
  
  container dhcp {
    
    description
      "configuration and operational parameters for a DHCP server.";
    
    leaf max-lease-time {
      type uint32;
      units seconds;
      default 7200;
    }
 
    leaf default-lease-time {
      type uint32;
      units seconds;
      must 'current() <= ../max-lease-time' {
	error-message
	  "The default-lease-time must be less than max-lease-time";
      }
      default 600;
    }
    
    uses subnet-list;
    
    container shared-networks {
      list shared-network {
	key name;
	
	leaf name { type string; }
	uses subnet-list;
      }
    }
    
    container status {
      config false;
      list leases {
	key address;
	
	leaf address { type inet:ip-address; }
	leaf starts { type yang:date-and-time; }
	leaf ends { type yang:date-and-time; }
	
	container hardware {
	  leaf type {
	    type enumeration {
	      enum "ethernet";
	      enum "token-ring";
	      enum "fddi";
	    }
	  }
	  leaf address { type yang:phys-address; }
	}
      }
    }
  }

  grouping subnet-list {
    description "A reusable list of subnets";
    list {
      key net;
      leaf net {
	type inet:ip-prefix;
      }
    }
    container range {
      presence "enables dynamic address assignment";
      leaf dynamic-bootp {
	type empty;
	description
	  "Allows BOOTP clients to get addresses in this range";
      }
      leaf low {
	type inet:ip-address;
	mandatory true;
      }
      leaf high {
	type inet:ip-address;
	mandatory true;
      }
    }
  
    container dhcp-options {
      description "Options in the dhcp protocol";
      leaf-list router {
	type inet:host;
	ordered-by user;
	reference "RFC 2132, sec 3.8";
      }
      leaf domain-name {
	type inet:domain-name;
	reference "RFC 2132, sec 3.17"
      }
    }
    
    leaf max-lease-time {
      type uint32;
      uints seconds;
      default 7200;
    }
  }
}
